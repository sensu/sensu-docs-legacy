-- Backward ported from Sensu Enterprise V2 to V1 MIB format

SENSU-ENTERPRISE-V1-MIB DEFINITIONS ::= BEGIN

IMPORTS
	enterprises
		FROM RFC1155-SMI
	OBJECT-TYPE
		FROM RFC-1212
	TRAP-TYPE
		FROM RFC-1215;

-- sensuEnterprise MODULE-IDENTITY
--     LAST-UPDATED "201508170000Z"
--     ORGANIZATION
--         "Sensu Enterprise"
--     CONTACT-INFO
--         "Sean Porter
--
--          Telephone: 1-855-99-SENSU
--          Email: helpdesk@sensuapp.com
--
--          Sensu Enterprise Information:
--            http://www.sensuapp.org/enterprise"
--     DESCRIPTION
--         "Objects for the Sensu Enterprise SNMP integration"
--     REVISION    "201508170000Z"
--     DESCRIPTION
--         "Added check output object, changing several OIDs"
--     REVISION    "201504200000Z"
--     DESCRIPTION
--         "Initial Version"
--     ::= { enterprises 45717 }

CheckSeverity ::= INTEGER {
		ok (0),
		warning (1),
		critical (2),
		unknown (3)
	}


EventAction ::= INTEGER {
		create (0),
		resolve (1),
		flapping (2)
	}

sensuEnterprise        OBJECT IDENTIFIER ::= { enterprises 45717 }
sensuEnterpriseNotify  OBJECT IDENTIFIER ::= { sensuEnterprise 1 }

sensuEnterpriseEventTable  OBJECT-TYPE
	SYNTAX SEQUENCE OF SensuEnterpriseEventEntry
	ACCESS     not-accessible
	STATUS     mandatory
	DESCRIPTION
		""
	::= { sensuEnterpriseNotify 1 }

-- A Sensu Enterprise event entry.

SensuEnterpriseEventEntry ::= SEQUENCE {
	sensuEventID
		OCTET STRING,
	sensuNotification
		OCTET STRING,
	sensuClientName
		OCTET STRING,
	sensuCheckName
		OCTET STRING,
	sensuCheckSeverity
		CheckSeverity,
	sensuCheckOutput
		OCTET STRING,
	sensuEventAction
		EventAction,
	sensuEventTimestamp
		INTEGER,
	sensuEventOccurrences
		INTEGER
}

sensuEnterpriseEventEntry  OBJECT-TYPE
	SYNTAX     SensuEnterpriseEventEntry
	ACCESS     not-accessible
	STATUS     mandatory
	DESCRIPTION
		"A Sensu Enterprise event entry."
	INDEX { sensuEventID }
	::= { sensuEnterpriseEventTable 1 }

-- This object uniquely identifies this event entry.

sensuEventID  OBJECT-TYPE
	SYNTAX     OCTET STRING
	ACCESS     read-only
	STATUS     mandatory
	DESCRIPTION
		""
	::= { sensuEnterpriseEventEntry 1 }

-- Event notification message.

sensuNotification  OBJECT-TYPE
	SYNTAX     OCTET STRING
	ACCESS     read-only
	STATUS     mandatory
	DESCRIPTION
		""
	::= { sensuEnterpriseEventEntry 2 }

-- Sensu client name.

sensuClientName  OBJECT-TYPE
	SYNTAX     OCTET STRING
	ACCESS     read-only
	STATUS     mandatory
	DESCRIPTION
		""
	::= { sensuEnterpriseEventEntry 3 }

-- Sensu check name.

sensuCheckName  OBJECT-TYPE
	SYNTAX     OCTET STRING
	ACCESS     read-only
	STATUS     mandatory
	DESCRIPTION
		""
	::= { sensuEnterpriseEventEntry 4 }

-- A number that corresponds to the current check status severity:
--    0=OK, 1=WARNING, 2=CRITICAL, 3=UNKNOWN

sensuCheckSeverity  OBJECT-TYPE
	SYNTAX     CheckSeverity
	ACCESS     read-only
	STATUS     mandatory
	DESCRIPTION
		""
	::= { sensuEnterpriseEventEntry 5 }

-- A string identifying the current event action (CREATE, RESOLVE,
--    FLAPPING).

-- Sensu check output.

sensuCheckOutput  OBJECT-TYPE
	SYNTAX     OCTET STRING
	ACCESS     read-only
	STATUS     mandatory
	DESCRIPTION
		""
	::= { sensuEnterpriseEventEntry 6 }

sensuEventAction  OBJECT-TYPE
	SYNTAX     EventAction
	ACCESS     read-only
	STATUS     optional
	DESCRIPTION
		""
	::= { sensuEnterpriseEventEntry 7 }

-- The event timestamp (seconds since the UNIX epoch).

sensuEventTimestamp  OBJECT-TYPE
	SYNTAX     INTEGER
	ACCESS     read-only
	STATUS     optional
	DESCRIPTION
		""
	::= { sensuEnterpriseEventEntry 8 }

-- The event occurrence count.

sensuEventOccurrences  OBJECT-TYPE
	SYNTAX     INTEGER
	ACCESS     read-only
	STATUS     mandatory
	DESCRIPTION
		""
	::= { sensuEnterpriseEventEntry 9 }

sensuEnterpriseEventTrap  TRAP-TYPE
	ENTERPRISE sensuEnterprise
	VARIABLES { sensuEventID,
                  sensuNotification,
                  sensuClientName,
                  sensuCheckName,
                  sensuCheckSeverity,
                  sensuCheckOutput,
                  sensuEventAction,
                  sensuEventTimestamp,
                  sensuEventOccurrences
		 }
	DESCRIPTION
		"The SNMP trap that is sent from Sensu Enterprise for an event."
	::= 0
END
