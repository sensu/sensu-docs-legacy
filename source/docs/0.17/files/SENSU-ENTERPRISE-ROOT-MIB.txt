SENSU-ENTERPRISE-ROOT-MIB DEFINITIONS ::= BEGIN
IMPORTS
  MODULE-IDENTITY, enterprises
    FROM SNMPv2-SMI
  TEXTUAL-CONVENTION
    FROM SNMPv2-TC;

sensuEnterprise MODULE-IDENTITY
  LAST-UPDATED "201504200000Z" -- April 20, 2015
  ORGANIZATION "Sensu Enterprise"
  CONTACT-INFO
    "Sean Porter

    Telephone: 1-855-99-SENSU
    Email: support@sensuapp.org

    Sensu Enterprise Information:
      http://www.sensuapp.org/enterprise
    "
  DESCRIPTION
    "Objects for the Sensu Enterprise SNMP integration"
  REVISION "201504200000Z" -- April 20, 2015
  DESCRIPTION
    "Initial Version"
  ::= {enterprises 45715}

--
-- Textual Conventions
--

EventAction ::= TEXTUAL-CONVENTION
  STATUS current
  DESCRIPTION
    "A string identifying the current event action (CREATE, RESOLVE,
    FLAPPING)."
  SYNTAX INTEGER {
    create(0),
    resolve(1),
    flapping(2)
    }

CheckSeverity ::= TEXTUAL-CONVENTION
  STATUS current
  DESCRIPTION
    "A number that corresponds to the current state of the service:
    0=OK, 1=WARNING, 2=CRITICAL, 3=UNKNOWN."
  SYNTAX INTEGER{
    ok(0),
    warning(1),
    critical(2),
    unknown(3)
    }

END
